module connect-point{
	yang-version 1;
	namespace "urn:onos:yangpromotion:def:link:connect:point";
	prefix "cp";

	import yang-ext {prefix ext; revision-date "2013-07-09";}
	import config {prefix config; revision-date "2015-10-01";}

	revision "2015-10-01" {
		description
		  "onos core connect point defination.";
	}

    typedef port-number{
       type int32;
    }

    grouping connect-point {
        choice element-id {
            case host-id{
              leaf host-id {
                type string;
              }
            }
            case ip-element-id {
              leaf ip-element-id{
                type string;
              }
            }
            case device-id {
              leaf device-id {
                type string;
              }
            }
        }
        leaf port-number {
           type port-number;
        }
    }

}
